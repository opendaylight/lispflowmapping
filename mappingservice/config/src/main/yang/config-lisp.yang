module config-lisp {
    yang-version 1;
    namespace "lispconfig";
    prefix "lispconfig";

    import config { prefix config; revision-date 2013-04-05; }
    import rpc-context { prefix rpcx; revision-date 2013-06-17; }

    organization "Contextream, Inc.";

    description
        "This module contains the base YANG definitions for lisp configuration.";

    revision "2013-11-07" {
        description
            "Initial revision.";
    }

    identity lispconfig {
        description
            "Actual state of lisp configuration.";
        base config:module-type;
        config:java-name-prefix LispConfig;
    }

    identity lispconfig-rpc;

    augment "/config:modules/config:module/config:configuration" {
        case lispconfig {
            when "/config:modules/config:module/config:type = 'lispconfig'";

            leaf bind-address {
   				type string;
            	mandatory true;
            }
        }
    }


    augment "/config:modules/config:module/config:state" {
        case lispconfig {
            when "/config:modules/config:module/config:type = 'lispconfig'";

            rpcx:rpc-context-instance "lispconfig-rpc";

        }
    }

    //rpc rpcmethodexample {
    //    input {
     //       uses rpcx:rpc-context-ref {
      //          refine context-instance {
       //             rpcx:rpc-context-instance lispconfig-rpc;
        //        }
         //   }
       // }
  //  }

}
