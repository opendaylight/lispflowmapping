module lfm-mapping-database {

    yang-version 1;
    namespace "urn:opendaylight:lfm-mapping-database";
    prefix "lfm-mapping-database";

    import ietf-inet-types { prefix inet; revision-date 2010-09-24; }
    import yang-ext { prefix ext; revision-date "2013-07-09"; }
    import lfm-control-plane { prefix lfm-cp; revision-date 2015-03-14; }

    contact "Lorand Jakab <lojakab@cisco.com";

    description
        "An MD-SAL based implementation of a LISP Map-Server database";

    revision "2015-03-14" {
        description "Initial revision.";
    }

    typedef mapping-origin {
        description "The originating entity of an EID-to-RLOC mapping";
        type enumeration {
            enum northbound;
            enum southbound;
        }
    }

    typedef site-id {
        description "64 bit site identifier";
        type binary {
            length "8";
        }
    }

    typedef iid-uri {
        description "IID as a string lookup key in a URI";
        type inet:uri;
    }

    typedef eid-uri {
        description "EID as a string lookup key in a URI";
        type inet:uri;
    }

    identity instance-id-context {
        description "A classifier for instance-id elements which allows direct access to a particular element in the data tree.";
    }

    identity eid-context {
        description "A classifier for endpoint-id elements which allows direct access to a particular element in the data tree.";
    }

    grouping lisp-prefix {
        uses lfm-cp:LispAddress;
        leaf mask-length {
            type uint8;
        }
    }

    grouping mapping-authkey {
        leaf key-type {
            type uint16;
        }
        leaf authkey {
            type string;
        }
    }

    grouping db-instance {
        description "Describes the mappings belonging to the same Instance ID";
        leaf iid {
            description "The 24-bit Instance ID";
            type iid-uri;
        }
        list mapping {
            description "A list of EID-to-RLOC mappings within the same Instance ID";
            key "eid origin";
            ext:context-instance "eid-context";
            leaf eid {
                type eid-uri;
            }
            leaf origin {
                type mapping-origin;
            }
            leaf-list site-id {
                type site-id;
            }
            uses lfm-cp:EidToLocatorRecord;
        }
        list authentication-key {
            description "A list of authentication keys for EID prefixes within the same Instance ID";
            key "eid";
            ext:context-instance "eid-context";
            leaf eid {
                type eid-uri;
            }
            uses lisp-prefix;
            uses mapping-authkey;
        }
    }

    container mapping-database {
        description "The LISP EID-to-RLOC mapping database";
        list instance-id {
            description "A list of LISP Instance IDs";
            key "iid";
            ext:context-instance "instance-id-context";
            uses db-instance;
        }
    }

    rpc add-key {
        input {
            uses lisp-prefix;
            uses mapping-authkey;
        }
    }

    rpc get-key {
        input {
            uses lisp-prefix;
        }
        output {
            uses mapping-authkey;
        }
    }

    rpc update-key {
        input {
            container eid {
                uses lisp-prefix;
            }
            container key {
                uses mapping-authkey;
            }
        }
    }

    rpc remove-key {
        input {
            uses lisp-prefix;
        }
    }

    rpc add-mapping {
        input {
            uses lfm-cp:EidToLocatorRecord;
        }
    }

    rpc get-mapping {
        input {
            uses lisp-prefix;
        }
        output {
            uses lfm-cp:EidToLocatorRecords;
        }
    }

    rpc update-mapping {
        input {
            uses lfm-cp:EidToLocatorRecord;
        }
    }

    rpc remove-mapping {
        input {
            uses lisp-prefix;
        }
    }
}
