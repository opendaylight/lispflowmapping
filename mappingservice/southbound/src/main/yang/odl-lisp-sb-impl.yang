module odl-lisp-sb-impl {

    yang-version 1;
    namespace "urn:opendaylight:params:xml:ns:yang:controller:config:lisp-sb:impl";
    prefix "lisp-sb-impl";

    import config { prefix config; revision-date 2013-04-05; }
    import rpc-context { prefix rpcx; revision-date 2013-06-17; }
    import opendaylight-md-sal-binding { prefix mdsal; revision-date 2013-10-28; }
    import opendaylight-sal-binding-broker-impl { prefix sal-broker; revision-date 2013-10-28; }
    import odl-lisp-sb { prefix lisp-sb; revision-date 2015-09-04; }
    import opendaylight-entity-ownership-service { prefix ownership-service; revision-date 2015-08-10;}

    description
        "This module contains the base YANG definitions for
        mappingservice southbound plugin implementation.";

    revision "2015-05-17" {
        description
            "Initial revision.";
    }

    identity lisp-sb-impl {
        base config:module-type;
        config:provided-service lisp-sb:lisp-sb;
        config:java-name-prefix LfmMappingServiceSb;
    }


    // Augments the 'configuration' choice node under modules/module.
    augment "/config:modules/config:module/config:configuration" {
        case lisp-sb-impl {
            when "/config:modules/config:module/config:type = 'lisp-sb-impl'";

            container notification-publish-service {
                uses config:service-ref {
                    refine type {
                        mandatory true;
                        config:required-identity sal-broker:binding-new-notification-publish-service;
                    }
                }
            }

            container rpc-registry {
                uses config:service-ref {
                    refine type {
                        mandatory true;
                        config:required-identity mdsal:binding-rpc-registry;
                    }
                }
            }

            container data-broker {
                uses config:service-ref {
                    refine type {
                        mandatory true;
                        config:required-identity mdsal:binding-async-data-broker;
                    }
                }
            }
            container entity-ownership-service {
                uses config:service-ref {
                    refine type {
                        mandatory true;
                        config:required-identity ownership-service:entity-ownership-service;
                    }
                }
            }
            leaf bind-address {
                type string;
                mandatory true;
            }

            leaf map-register-cache {
                type boolean;
                mandatory true;
            }

        }
    }
}
