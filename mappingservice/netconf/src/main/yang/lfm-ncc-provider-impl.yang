module lfm-ncc-provider-impl {
    yang-version 1;
    namespace "urn:opendaylight:params:xml:ns:yang:controller:config:lfm-netconf:impl";
    prefix "lfm-ncc-provider-impl";

    import config { prefix config; revision-date 2013-04-05; }
    import opendaylight-md-sal-binding { prefix mdsal; revision-date 2013-10-28; }

    description
        "This module contains the base YANG definitions for lispflowmapping-netconf-connector implementation.";

    revision "2014-07-06" {
        description
            "Initial revision.";
    }

    identity lfm-ncc-provider-impl {
        base config:module-type;
        config:java-name-prefix LfmNetconfConnectorProvider;
    }

    augment "/config:modules/config:module/config:configuration" {
        case lfm-ncc-provider-impl {
            when "/config:modules/config:module/config:type = 'lfm-ncc-provider-impl'";

            container rpc-registry {
                uses config:service-ref {
                    refine type {
                        mandatory true;
                        config:required-identity mdsal:binding-rpc-registry;
                    }
                }
            }
        }
    }
}
