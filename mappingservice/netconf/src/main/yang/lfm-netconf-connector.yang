module lfm-netconf-connector {
    yang-version 1;

    namespace "urn:opendaylight:params:xml:ns:yang:lispflowmapping:netconf";
    prefix "lnc";

    import config { prefix config; revision-date 2013-04-05; }
    import ietf-inet-types { prefix inet; revision-date "2013-07-15"; }

    organization "Cisco Systems, Inc.";

    contact
      "Florin Coras <fcoras@ac.upc.edu>";

    revision "2014-07-06" {
        description
          "Data model for lispflowmapping netconf connector";
    }

    container nc-connector {
        presence
        "Indicates the netconf connector service is available";

        description
        "Top-level container for all connector database objects.";
    }

    rpc build-connector {
        description
           "Build netconf connector";
        input {
            leaf instance {
                type string;
                description "instance name";
            }

            leaf address {
                 type inet:host;
                 description "Device address";
            }

            leaf port {
                type inet:port-number;
                description "Device port";
            }

            leaf username {
                type string;
                description "Username for netconf connection";
            }

            leaf password {
                type string;
                description "Password for netconf connection";
            }
        }
    }

    rpc remove-connector {
        description
            "Removes a given netconf connector";
        input {
            leaf instance {
                type string;
                description "instance name";
            }
        }
    }
}
