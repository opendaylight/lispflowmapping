module odl-mappingservice-dao {
    yang-version 1;
    namespace "urn:opendaylight:lfm:mappingservice-dao";
    prefix "ms-dao";

    import config { prefix config; revision-date 2013-04-05; }

    description
        "Service definition for Mapping Service DAO.";

    revision "2015-10-07" {
        description
            "Module renamed from lfm-ms-dao.";
    }

    identity mappingservice-dao {
        base "config:service-type";
        config:java-class "org.opendaylight.lispflowmapping.interfaces.dao.ILispDAO";
    }
}
