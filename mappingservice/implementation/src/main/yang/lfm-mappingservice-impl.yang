module lfm-mappingservice-impl {

  yang-version 1;
  namespace "urn:opendaylight:params:xml:ns:yang:controller:config:lfm-mappingservice:impl";
  prefix "lfm-mappingservice-impl";

  import config { prefix config; revision-date 2013-04-05; }
  import rpc-context { prefix rpcx; revision-date 2013-06-17; }
  import opendaylight-md-sal-binding { prefix mdsal; revision-date 2013-10-28; }
  import lfm-ms-dao { prefix ms-dao; revision-date 2015-07-13; }

  description
      "This module contains the base YANG definitions for
      mappingservice implementation.";

  revision "2015-05-17" {
      description
          "Initial revision.";
  }

  // This is the definition of lfm-mappingservice interface identity.
  identity lfm-mappingservice {
      base config:service-type;
      config:java-class "org.opendaylight.lispflowmapping.interfaces.lisp.IFlowMapping";
  }
  
  // This is the definition of the lfm-mappingservice implementation as a module identity
  identity lfm-mappingservice-impl {
      base config:module-type;

      // Specifies the prefix for generated java classes.
      config:java-name-prefix LfmMappingService;
      config:provided-service lfm-mappingservice;
  }

  // Augments the 'configuration' choice node under modules/module.
  augment "/config:modules/config:module/config:configuration" {
    case lfm-mappingservice-impl {
      when "/config:modules/config:module/config:type = 'lfm-mappingservice-impl'";

      //wires in the data-broker service
      container data-broker {
        uses config:service-ref {
          refine type {
              mandatory true;
              config:required-identity mdsal:binding-async-data-broker;
          }
        }
      }
      container broker {
          uses config:service-ref {
              refine type {
                  mandatory true;
                  config:required-identity mdsal:binding-broker-osgi-registry;
              }
          }
      }
      container rpc-registry {
        uses config:service-ref {
          refine type {
              mandatory true;
              config:required-identity mdsal:binding-rpc-registry;
          }
        }
      }
      container dao {
          uses config:service-ref {
              refine type {
                  mandatory true;
                  config:required-identity ms-dao:ms-dao;
              }
          }
      }
    }
  }
}
