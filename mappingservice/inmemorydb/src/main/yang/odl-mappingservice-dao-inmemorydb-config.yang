module odl-mappingservice-dao-inmemorydb-config {
    yang-version 1;
    namespace "urn:opendaylight:params:xml:ns:yang:controller:config:lfm:mappingservice-dao:inmemorydb:config";
    prefix "inmemorydb";

    description
        "InMemoryDb Mapping Service DAO config.";

    revision "2015-10-07" {
        description
                "Config file for inmemorydb";
    }

    container inmemorydb-config {
        leaf record-timeout {
            type uint16;
            default 240;
            description "Mapping record timeout";
        }
    }
}
