module odl-lisp-binary-address-types {

    yang-version 1;
    namespace "urn:opendaylight:lfm:lisp-binary-address-types";
    prefix "lisp-binary";

    import ietf-lisp-address-types { prefix laddr; revision-date 2015-11-05; }
    import odl-inet-binary-types { prefix bin; revision-date 2016-03-03; }
    import odl-lisp-proto { prefix lisp; revision-date 2015-11-05; }

    contact
        "Lori Jakab <lojakab@cisco.com>";

    description
        "Augments for ietf-lisp-address-types to support binary IPv4 and IPv6
         addresses and prefixes internally in OpenDaylight";

    revision "2016-03-03" {
        description "Initial revision.";
    }

    identity ipv4-binary-afi {
        base laddr:lisp-address-family;
        description
            "IANA IPv4 address family (binary representation).";
    }

    identity ipv6-binary-afi {
        base laddr:lisp-address-family;
        description
            "IANA IPv6 address family (binary representation).";
    }
}
